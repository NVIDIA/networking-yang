module nvidia-ietf-interfaces-notsupported-deviations {
  namespace "http://nvidia.com/yang/ietf/interfaces/not-supported-deviations";
  prefix nvidia-interfaces-notsupported-deviations;

  import ietf-interfaces {
    prefix if;
  }

  organization
    "Nvidia https://www.nvidia.com";
  contact
    "NVIDIA CORPORATION & AFFILIATES
    www.nvidia.com";
  description
    "This module contains ietf interfaces not-supported deviations.

    Copyright (c) 2026 NVIDIA CORPORATION & AFFILIATES. All rights reserved.";

  revision 2026-03-18 {
    description
      "Auto-generated not-supported deviations for unsupported paths";
  }

  deviation /if:interfaces {
    description "Not supported";
    deviate not-supported;
  }

  deviation /if:interfaces-state {
    description "Not supported";
    deviate not-supported;
  }
}
