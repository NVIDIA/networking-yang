module nvidia-openconfig-interfaces-notsupported-deviations {
  namespace "http://nvidia.com/yang/openconfig/interfaces/not-supported-deviations";
  prefix nvidia-interfaces-notsupported-deviations;

  import openconfig-interfaces {
    prefix oc-if;
  }

  import openconfig-vlan {
    prefix oc-vlan;
  }

  import openconfig-if-aggregate {
    prefix oc-lag;
  }

  import openconfig-if-rates {
    prefix oc-if-rates;
  }

  import nvidia-if-ethernet-augments {
    prefix nvidia-if-eth-augments;
  }

  import nvidia-if-phy-augments {
    prefix nvidia-if-phy-augments;
  }

  import openconfig-platform-port {
    prefix oc-port;
  }

  import openconfig-if-ethernet {
    prefix oc-eth;
  }

  import openconfig-if-8021x {
    prefix oc-1x;
  }

  import openconfig-platform-transceiver {
    prefix oc-transceiver;
  }

  organization
    "Nvidia https://www.nvidia.com";
  contact
    "NVIDIA CORPORATION & AFFILIATES
    www.nvidia.com";
  description
    "This module contains openconfig interfaces not-supported deviations.

    Copyright (c) 2026 NVIDIA CORPORATION & AFFILIATES. All rights reserved.";

  revision 2026-03-18 {
    description
      "Auto-generated not-supported deviations for unsupported paths";
  }

  deviation /oc-if:interfaces/oc-if:interface/oc-if:penalty-based-aied {
    description "Not supported";
    deviate not-supported;
  }

  deviation /oc-if:interfaces/oc-if:interface/oc-if:hold-time {
    description "Not supported";
    deviate not-supported;
  }

  deviation /oc-if:interfaces/oc-if:interface/oc-if:config/oc-vlan:tpid {
    description "Not supported";
    deviate not-supported;
  }

  deviation /oc-if:interfaces/oc-if:interface/oc-if:config/oc-if:mtu {
    description "Not supported";
    deviate not-supported;
  }

  deviation /oc-if:interfaces/oc-if:interface/oc-if:config/oc-if:enabled {
    description "Not supported";
    deviate not-supported;
  }

  deviation /oc-if:interfaces/oc-if:interface/oc-if:config/oc-if:loopback-mode {
    description "Not supported";
    deviate not-supported;
  }

  deviation /oc-if:interfaces/oc-if:interface/oc-if:config/oc-if:description {
    description "Not supported";
    deviate not-supported;
  }

  deviation /oc-if:interfaces/oc-if:interface/oc-if:config/oc-if:type {
    description "Not supported";
    deviate not-supported;
  }

  deviation /oc-if:interfaces/oc-if:interface/oc-lag:aggregation {
    description "Not supported";
    deviate not-supported;
  }

  deviation /oc-if:interfaces/oc-if:interface/oc-eth:ethernet/nvidia-if-eth-augments:phy {
    description "Not supported";
    deviate not-supported;
  }

  deviation /oc-if:interfaces/oc-if:interface/oc-eth:ethernet/oc-eth:config {
    description "Not supported";
    deviate not-supported;
  }

  deviation /oc-if:interfaces/oc-if:interface/oc-eth:ethernet/oc-eth:state/oc-eth:counters/oc-eth:out-mac-control-frames {
    description "Not supported";
    deviate not-supported;
  }

  deviation /oc-if:interfaces/oc-if:interface/oc-eth:ethernet/oc-eth:state/oc-eth:counters/oc-eth:in-mac-control-frames {
    description "Not supported";
    deviate not-supported;
  }

  deviation /oc-if:interfaces/oc-if:interface/oc-eth:ethernet/oc-eth:state/oc-eth:counters/oc-eth:out-8021q-frames {
    description "Not supported";
    deviate not-supported;
  }

  deviation /oc-if:interfaces/oc-if:interface/oc-eth:ethernet/oc-eth:state/oc-eth:counters/oc-eth:in-late-collision {
    description "Not supported";
    deviate not-supported;
  }

  deviation /oc-if:interfaces/oc-if:interface/oc-eth:ethernet/oc-eth:state/oc-eth:counters/oc-eth:in-mac-errors-rx {
    description "Not supported";
    deviate not-supported;
  }

  deviation /oc-if:interfaces/oc-if:interface/oc-eth:ethernet/oc-eth:state/oc-eth:counters/oc-eth:in-8021q-frames {
    description "Not supported";
    deviate not-supported;
  }

  deviation /oc-if:interfaces/oc-if:interface/oc-eth:ethernet/oc-eth:state/oc-eth:counters/oc-eth:in-interrupted-tx {
    description "Not supported";
    deviate not-supported;
  }

  deviation /oc-if:interfaces/oc-if:interface/oc-eth:ethernet/oc-eth:state/oc-eth:counters/oc-eth:out-mac-errors-tx {
    description "Not supported";
    deviate not-supported;
  }

  deviation /oc-if:interfaces/oc-if:interface/oc-eth:ethernet/oc-eth:state/oc-eth:counters/oc-eth:in-block-errors {
    description "Not supported";
    deviate not-supported;
  }

  deviation /oc-if:interfaces/oc-if:interface/oc-eth:ethernet/oc-eth:state/oc-eth:counters/oc-eth:in-carrier-errors {
    description "Not supported";
    deviate not-supported;
  }

  deviation /oc-if:interfaces/oc-if:interface/oc-eth:ethernet/oc-eth:state/oc-eth:counters/oc-eth:in-single-collision {
    description "Not supported";
    deviate not-supported;
  }

  deviation /oc-if:interfaces/oc-if:interface/oc-eth:ethernet/oc-eth:state/oc-eth:duplex-mode {
    description "Not supported";
    deviate not-supported;
  }

  deviation /oc-if:interfaces/oc-if:interface/oc-eth:ethernet/oc-eth:state/oc-eth:standalone-link-training {
    description "Not supported";
    deviate not-supported;
  }

  deviation /oc-if:interfaces/oc-if:interface/oc-eth:ethernet/oc-eth:state/oc-lag:aggregate-id {
    description "Not supported";
    deviate not-supported;
  }

  deviation /oc-if:interfaces/oc-if:interface/oc-eth:ethernet/oc-eth:state/oc-eth:enable-flow-control {
    description "Not supported";
    deviate not-supported;
  }

  deviation /oc-if:interfaces/oc-if:interface/oc-eth:ethernet/oc-eth:state/oc-eth:fec-mode {
    description "Not supported";
    deviate not-supported;
  }

  deviation /oc-if:interfaces/oc-if:interface/oc-eth:ethernet/oc-vlan:switched-vlan {
    description "Not supported";
    deviate not-supported;
  }

  deviation /oc-if:interfaces/oc-if:interface/oc-eth:ethernet/oc-1x:dot1x/oc-1x:state/oc-1x:retransmit-interval {
    description "Not supported";
    deviate not-supported;
  }

  deviation /oc-if:interfaces/oc-if:interface/oc-eth:ethernet/oc-1x:dot1x/oc-1x:state/oc-1x:max-requests {
    description "Not supported";
    deviate not-supported;
  }

  deviation /oc-if:interfaces/oc-if:interface/oc-eth:ethernet/oc-1x:dot1x/oc-1x:state/oc-1x:server-fail-vlan {
    description "Not supported";
    deviate not-supported;
  }

  deviation /oc-if:interfaces/oc-if:interface/oc-eth:ethernet/oc-1x:dot1x/oc-1x:state/oc-1x:supplicant-timeout {
    description "Not supported";
    deviate not-supported;
  }

  deviation /oc-if:interfaces/oc-if:interface/oc-eth:ethernet/oc-1x:dot1x/oc-1x:state/oc-1x:authenticate-port {
    description "Not supported";
    deviate not-supported;
  }

  deviation /oc-if:interfaces/oc-if:interface/oc-eth:ethernet/oc-1x:dot1x/oc-1x:config {
    description "Not supported";
    deviate not-supported;
  }

  deviation /oc-if:interfaces/oc-if:interface/oc-vlan:routed-vlan {
    description "Not supported";
    deviate not-supported;
  }

  deviation /oc-if:interfaces/oc-if:interface/nvidia-if-phy-augments:phy/nvidia-if-phy-augments:operation-information {
    description "Not supported";
    deviate not-supported;
  }

  deviation /oc-if:interfaces/oc-if:interface/nvidia-if-phy-augments:phy/nvidia-if-phy-augments:fec/nvidia-if-phy-augments:state/nvidia-if-phy-augments:profile-fec-in-use {
    description "Not supported";
    deviate not-supported;
  }

  deviation /oc-if:interfaces/oc-if:interface/nvidia-if-phy-augments:phy/nvidia-if-phy-augments:fec/nvidia-if-phy-augments:state/nvidia-if-phy-augments:zero-hist {
    description "Not supported";
    deviate not-supported;
  }

  deviation /oc-if:interfaces/oc-if:interface/nvidia-if-phy-augments:phy/nvidia-if-phy-augments:fec/nvidia-if-phy-augments:state/nvidia-if-phy-augments:fec-mode-request {
    description "Not supported";
    deviate not-supported;
  }

  deviation /oc-if:interfaces/oc-if:interface/nvidia-if-phy-augments:phy/nvidia-if-phy-augments:ber/nvidia-if-phy-augments:state/nvidia-if-phy-augments:raw-ber {
    description "Not supported";
    deviate not-supported;
  }

  deviation /oc-if:interfaces/oc-if:interface/nvidia-if-phy-augments:phy/nvidia-if-phy-augments:infiniband {
    description "Not supported";
    deviate not-supported;
  }

  deviation /oc-if:interfaces/oc-if:interface/nvidia-if-phy-augments:phy/nvidia-if-phy-augments:channels/nvidia-if-phy-augments:channel/nvidia-if-phy-augments:state/nvidia-if-phy-augments:id {
    description "Not supported";
    deviate not-supported;
  }

  deviation /oc-if:interfaces/oc-if:interface/nvidia-if-phy-augments:phy/nvidia-if-phy-augments:link-down-information {
    description "Not supported";
    deviate not-supported;
  }

  deviation /oc-if:interfaces/oc-if:interface/nvidia-if-phy-augments:phy/nvidia-if-phy-augments:recovery-information {
    description "Not supported";
    deviate not-supported;
  }

  deviation /oc-if:interfaces/oc-if:interface/nvidia-if-phy-augments:phy/nvidia-if-phy-augments:nvlink {
    description "Not supported";
    deviate not-supported;
  }

  deviation /oc-if:interfaces/oc-if:interface/nvidia-if-phy-augments:phy/nvidia-if-phy-augments:state/nvidia-if-phy-augments:time-since-last-clear-min {
    description "Not supported";
    deviate not-supported;
  }

  deviation /oc-if:interfaces/oc-if:interface/oc-if:subinterfaces {
    description "Not supported";
    deviate not-supported;
  }

  deviation /oc-if:interfaces/oc-if:interface/oc-if:state/oc-if:logical {
    description "Not supported";
    deviate not-supported;
  }

  deviation /oc-if:interfaces/oc-if:interface/oc-if:state/oc-if:counters/oc-if:resets {
    description "Not supported";
    deviate not-supported;
  }

  deviation /oc-if:interfaces/oc-if:interface/oc-if:state/oc-if:counters/oc-if:last-clear {
    description "Not supported";
    deviate not-supported;
  }

  deviation /oc-if:interfaces/oc-if:interface/oc-if:state/oc-if:counters/oc-if:in-fcs-errors {
    description "Not supported";
    deviate not-supported;
  }

  deviation /oc-if:interfaces/oc-if:interface/oc-if:state/oc-if:cpu {
    description "Not supported";
    deviate not-supported;
  }

  deviation /oc-if:interfaces/oc-if:interface/oc-if:state/oc-if:loopback-mode {
    description "Not supported";
    deviate not-supported;
  }

  deviation /oc-if:interfaces/oc-if:interface/oc-if:state/oc-if:enabled {
    description "Not supported";
    deviate not-supported;
  }

  deviation /oc-if:interfaces/oc-if:interface/oc-if:state/oc-transceiver:physical-channel {
    description "Not supported";
    deviate not-supported;
  }

  deviation /oc-if:interfaces/oc-if:interface/oc-if:state/oc-if:management {
    description "Not supported";
    deviate not-supported;
  }

  deviation /oc-if:interfaces/oc-if:interface/oc-if:state/oc-port:hardware-port {
    description "Not supported";
    deviate not-supported;
  }

  deviation /oc-if:interfaces/oc-if:interface/oc-if:state/oc-vlan:tpid {
    description "Not supported";
    deviate not-supported;
  }

  deviation /oc-if:interfaces/oc-if:interface/oc-if-rates:rates/oc-if-rates:config {
    description "Not supported";
    deviate not-supported;
  }

  deviation /oc-if:interfaces/oc-if:interface/oc-if-rates:rates/oc-if-rates:state/oc-if-rates:load-interval {
    description "Not supported";
    deviate not-supported;
  }
}
