module nvidia-openconfig-bfd-notsupported-deviations {
  namespace "http://nvidia.com/yang/openconfig/bfd/not-supported-deviations";
  prefix nvidia-bfd-notsupported-deviations;

  import openconfig-bfd {
    prefix oc-bfd;
  }

  organization
    "Nvidia https://www.nvidia.com";
  contact
    "NVIDIA CORPORATION & AFFILIATES
    www.nvidia.com";
  description
    "This module contains openconfig bfd not-supported deviations.

    Copyright (c) 2026 NVIDIA CORPORATION & AFFILIATES. All rights reserved.";

  revision 2026-03-18 {
    description
      "Auto-generated not-supported deviations for unsupported paths";
  }

  deviation /oc-bfd:bfd {
    description "Not supported";
    deviate not-supported;
  }
}
