module nvidia-openconfig-defined-sets-notsupported-deviations {
  namespace "http://nvidia.com/yang/openconfig/defined-sets/not-supported-deviations";
  prefix nvidia-defined-sets-notsupported-deviations;

  import openconfig-defined-sets {
    prefix oc-sets;
  }

  organization
    "Nvidia https://www.nvidia.com";
  contact
    "NVIDIA CORPORATION & AFFILIATES
    www.nvidia.com";
  description
    "This module contains openconfig defined-sets not-supported deviations.

    Copyright (c) 2026 NVIDIA CORPORATION & AFFILIATES. All rights reserved.";

  revision 2026-03-18 {
    description
      "Auto-generated not-supported deviations for unsupported paths";
  }

  deviation /oc-sets:defined-sets {
    description "Not supported";
    deviate not-supported;
  }
}
