module nvidia-openconfig-routing-policy-notsupported-deviations {
  namespace "http://nvidia.com/yang/openconfig/routing-policy/not-supported-deviations";
  prefix nvidia-routing-policy-notsupported-deviations;

  import openconfig-routing-policy {
    prefix oc-rpol;
  }

  organization
    "Nvidia https://www.nvidia.com";
  contact
    "NVIDIA CORPORATION & AFFILIATES
    www.nvidia.com";
  description
    "This module contains openconfig routing-policy not-supported deviations.

    Copyright (c) 2026 NVIDIA CORPORATION & AFFILIATES. All rights reserved.";

  revision 2026-03-18 {
    description
      "Auto-generated not-supported deviations for unsupported paths";
  }

  deviation /oc-rpol:routing-policy {
    description "Not supported";
    deviate not-supported;
  }
}
