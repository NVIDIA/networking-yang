module nvidia-platform-storage-augments {

yang-version "1";

// namespace
namespace "http://openconfig.net/yang/openconfig/platform/storage/augments";

prefix "oc-storage-augments";

import openconfig-platform {
  prefix oc-platform;
}
import openconfig-platform-storage {
  prefix oc-storage;
}
import openconfig-extensions {
  prefix oc-ext;
}

// meta
organization
    "Nvidia https://www.nvidia.com";
  contact
    "NVIDIA CORPORATION & AFFILIATES
     www.nvidia.com";
  description
    "This module contains OpenConfig Storage augments in NVidia Cumulus OS.

     Copyright (c) 2025 NVIDIA CORPORATION & AFFILIATES. All rights reserved.";

oc-ext:openconfig-version "0.1.0";

revision "2025-11-19" {
  description
    "Added total size leaf.";
  reference
    "0.2";
}

revision "2024-08-26" {
  description
    "Initial revision.";
  reference
    "0.1";
}

// OpenConfig specific extensions for module metadata.
oc-ext:regexp-posix;
oc-ext:catalog-organization "openconfig";
oc-ext:origin "openconfig";

grouping storage-counters-state-augment {
    description
      "counters for storage";

    /* Additional storage counters */
    leaf rotation-rate-rpm {
      type uint64;
      units "rpm";
      description
        "Nominal spindle rotation rate in revolutions per minute. Applicable only for SATA devices.";
    }

    leaf write-cache {
      type boolean;
      description
        "Mode of the device write cache (for example, write-back or write-through). Applicable only for SATA devices.";
    }

    leaf write-cache-enabled {
      type boolean;
      description
        "Indicates whether the device write cache is enabled. Applicable only for SATA devices.";
    }

    leaf discard-seconds {
      type decimal64 { fraction-digits 3; }
      units "seconds";
      description
        "Total time spent servicing discard requests in seconds.";
    }

    leaf discard-sectors {
      type uint64;
      description
        "Total number of sectors discarded.";
    }

    leaf discard-completed {
      type uint64;
      description
        "Total number of discard requests completed.";
    }

    leaf discard-merged {
      type uint64;
      description
        "Total number of discard requests merged.";
    }

    leaf flush-req-seconds {
      type decimal64 { fraction-digits 3; }
      units "seconds";
      description
        "Total time spent processing flush requests in seconds.";
    }

    leaf flush-req {
      type uint64;
      description
        "Total number of flush requests issued.";
    }

    leaf io-ops-in-progress {
      type uint64;
      description
        "Current number of I/O operations in progress (in-flight).";
    }

    leaf io-seconds {
      type decimal64 { fraction-digits 3; }
      units "seconds";
      description
        "Total time the device has spent doing I/Os in seconds.";
    }

    leaf io-weighted-seconds {
      type decimal64 { fraction-digits 3; }
      units "seconds";
      description
        "Weighted time spent doing I/Os in seconds.";
    }

    leaf read-bytes {
      type uint64;
      units "bytes";
      description
        "Total bytes read from the device.";
    }

    leaf read-seconds {
      type decimal64 { fraction-digits 3; }
      units "seconds";
      description
        "Total time spent on read operations in seconds.";
    }

    leaf read-ops {
      type uint64;
      description
        "Total number of read I/O operations completed.";
    }

    leaf read-merged {
      type uint64;
      description
        "Total number of read requests merged.";
    }

    leaf write-bytes {
      type uint64;
      units "bytes";
      description
        "Total bytes written to the device.";
    }

    leaf write-seconds{
      type decimal64 { fraction-digits 3; }
      units "seconds";
      description
        "Total time spent on write operations in seconds.";
    }

    leaf write-ops {
      type uint64;
      description
        "Total number of write I/O operations completed.";
    }

    leaf write-merged {
      type uint64;
      description
        "Total number of write requests merged.";
    }
  }

  grouping storage-state-augment {
    description
      "State data for storage";

    leaf total-size {
      type uint64;
      units "bytes";
      description
        "Total size in bytes of the storage device.";
    }
  }

  // data definition statements
  // augment statements
  augment "/oc-platform:components/oc-platform:component/" +
    "oc-platform:storage/oc-platform:state" {
    description
      "Adding storage state data to component model";

    uses storage-state-augment;
  }

  augment "/oc-platform:components/oc-platform:component/" +
    "oc-platform:storage/oc-platform:state/oc-storage:counters" {
    description
      "Adding storage counters to component model";

    uses storage-counters-state-augment;
  }
}
