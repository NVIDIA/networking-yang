module nvidia-platform-fan-augments {

  yang-version "1";

  // namespace
  namespace "http://nvidia.com/yang/openconfig/platform/fan/augments";

  prefix "nvidia-fan-aug";

  import openconfig-platform { prefix oc-platform; }
  import openconfig-extensions { prefix oc-ext; }


  // meta
  organization
    "Nvidia https://www.nvidia.com";
  contact
    "NVIDIA CORPORATION & AFFILIATES
     www.nvidia.com";
  description
    "This module contains OpenConfig Fan augments in NVidia Cumulus OS.
     to support NVIDIA-specific extensions.
     Copyright (c) 2025 NVIDIA CORPORATION & AFFILIATES. All rights reserved.";
     
  oc-ext:openconfig-version "0.1.1";

  revision "2025-08-21" {
    description
      "Initial revision";
    reference "0.0.1";
  }

  // OpenConfig specific extensions for module metadata.
  oc-ext:regexp-posix;
  oc-ext:catalog-organization "openconfig";
  oc-ext:origin "openconfig";

  // identity statements

  // typedef statements

  // grouping statements

  grouping fan-state-augments {
    description
      "Operational state data for fan components";

    leaf direction {
        type string;
        description
          "Current fan direction F2B: Front to back, B2F: Back to front push";
    }

    leaf max-speed {
        type uint32;
        units rpm;
        description
          "Maximum fan speed";
    }

    leaf min-speed {
        type uint32;
        units rpm;
        description
          "Minimum fan speed";
    }
  }

  // augment statements
  augment "/oc-platform:components/oc-platform:component/" +
    "oc-platform:fan/oc-platform:state" {
    description
      "Adding fan data to component model";

    uses fan-state-augments;
  }
}
