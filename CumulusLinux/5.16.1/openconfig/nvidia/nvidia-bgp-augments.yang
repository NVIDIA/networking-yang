module nvidia-bgp-augments {
  yang-version 1.1;
  namespace "http://nvidia.com/yang/openconfig/bgp/augments";
  prefix nvidia-bgp-aug;

  import openconfig-network-instance { prefix oc-ni; }

  organization
    "Nvidia https://www.nvidia.com";
  contact
    "NVIDIA CORPORATION & AFFILIATES
     www.nvidia.com";
  description
    "This module contains OpenConfig bgp augments in NVidia Cumulus OS.

     Copyright (c) 2025 NVIDIA CORPORATION & AFFILIATES. All rights reserved.";

  revision 2025-07-17 {
    description
      "Initial bgp augment file.";
    reference
      "1.0.0";
  }
   augment "/oc-ni:network-instances/oc-ni:network-instance/oc-ni:protocols/oc-ni:protocol/oc-ni:bgp/oc-ni:neighbors/oc-ni:neighbor/oc-ni:state" {
    description
      "Adds additional gracefull shutdown state information at neighbor level";

    leaf graceful-shutdown {
      type boolean;
      description
        "State information for graceful shutdown at neighbor level";
    }
  }
}
