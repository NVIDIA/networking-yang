module nvidia-interfaces-augments {
  namespace "http://nvidia.com/yang/openconfig/interfaces/augments";
  prefix nvidia-interfaces-augments;

  import openconfig-interfaces {
    prefix oc-if;
  }
  import openconfig-yang-types {
    prefix oc-yang;
  }
  import openconfig-extensions {
    prefix oc-ext;
  }

  organization
    "NVidia Corporation <http://nvidia.com/>";
  contact
    "NVidia Corporation Product Support";
  description
    "This module contains OpenConfig interface augments in NVidia Cumulus OS.

     Copyright (c) 2024 NVIDIA CORPORATION & AFFILIATES. All rights reserved.";
  oc-ext:openconfig-version "1.0.0";

  revision 2025-09-16 {
    description
      "Added additional interface metrics.";
    reference
      "1.1.0";
  }

  revision 2025-07-02 {
    description
      "Add protodown support";
    reference
      "1.0.1";
  }

  revision 2025-04-14 {
    description
      "Initial augment file.";
    reference
      "1.0.0";
  }

  augment "/oc-if:interfaces/oc-if:interface/oc-if:state" {
    description
      "Add protodown field to indicate whether an interface is admin down or up";

    leaf protodown {
      type boolean;
      default false;
      config false;
      description
	"Indicates whether the interface is administratively held down by a protocol or system process rather than by user action";
    }
  }

  augment "/oc-if:interfaces/oc-if:interface/oc-if:state/oc-if:counters" {
    description
      "Add additional ingress/egress interface counters.";

    leaf in-acl-drops {
      type oc-yang:counter64;
      description
        "Number of packets dropped at ingress due to ACL Policy.";
    }

    leaf carrier-down-transitions {
      type oc-yang:counter64;
      description
        "Number of times that carrier down change happened on the interface.";
    }

    leaf carrier-up-transitions {
      type oc-yang:counter64;
      description
        "Number of times that carrier up change happened on the interface.";
    }

    leaf out-hoq-drops {
      type oc-yang:counter64;
      description
        "Number of packets dropped at egress due to Head-of-Queue Timeout.";
    }

    leaf out-hoq-stall-drops {
      type oc-yang:counter64;
      description
        "Number of sequential packets dropped, due to HeadOf-Queue Lifetime
        Limit, that causes the port to enter the Stall state.";
    }

    leaf out-sll-drops {
      type oc-yang:counter64;
      description
        "Number of packets dropped at egress due to Switch Lifetime Limit exceeds.";
    }

    leaf out-acl-drops {
      type oc-yang:counter64;
      description
        "Number of packets dropped at egress due to ACL Policy.";
    }

    leaf in-buffer-almost-full {
      type oc-yang:counter64;
      description
        "The number of events where the port rx buffer has passed a fullness threshold.";
    }

    leaf in-buffer-full {
      type oc-yang:counter64;
      description
        "The number of events where the port rx buffer has reached 100% fullness.";
    }

    leaf in-ebp-pkts {
      type oc-yang:counter64;
      description
        "The number of received EBP packets.";
    }

    leaf out-ebp-pkts {
      type oc-yang:counter64;
      description
        "The number of transmitted EBP packets.";
    }

    leaf tx-wait {
      type oc-yang:counter64;
      description
        "Number of TX wait events on this interface.";
    }

    leaf ecn-marked-pkts {
      type oc-yang:counter64;
      description
        "Number of packets that have been ECN marked on this interface.";
    }

    leaf ece-marked-pkts {
      type oc-yang:counter64;
      description
        "Number of packets that have been ECE marked on this interface.";
    }

    leaf in-unknown-protos {
      type oc-yang:counter64;
      description
        "Number of packets received with unknown protocols on this interface.";
    }

  }

}
