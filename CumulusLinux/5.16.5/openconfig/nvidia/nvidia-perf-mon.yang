module nvidia-perf-mon {
    namespace "http://nvidia.com/ns/performance-monitoring/1.0";
    prefix "nv-perf";
    
    organization
        "Nvidia https://www.nvidia.com";
    contact
        "NVIDIA CORPORATION & AFFILIATES
        www.nvidia.com";
    description
        "This module contains performance measurements in Nvidia Cumulus OS.

        Copyright (c) 2025 NVIDIA CORPORATION & AFFILIATES. All rights reserved.";

    revision 2026-05-13 {
        description
        "Tidy up description.";
    }

    revision 2025-12-10 {
        description
            "Added histogram metrics support for interface performance monitoring:
            - Egress buffer queue depth distribution per traffic class
            - Ingress buffer queue depth distribution per priority group
            - Interface counter value distributions (rx/tx bytes, packets, CRC, L1 bytes)
            - Packet latency distribution per traffic class
            - Added histogram-boundary typedef with '+Inf' support for unbounded upper limits";
        reference
            "0.1.0";
    }

    revision 2025-10-10 {
        description
            "Initial revision";
        reference
            "0.0.1";
    }

    // typedef statements
    typedef histogram-boundary {
        type union {
            type uint64;
            type enumeration {
                enum "+Inf" {
                    description "Positive infinity - represents an unbounded upper limit";
                }
            }
        }
        description
            "Type definition for histogram bucket upper boundaries. 
             Accepts either a numeric uint64 value or the special value '+Inf'
             to represent positive infinity for the last bucket.";
    }

    container performance {
        config false;
        description "Network performance monitoring telemetry data";
        
        container interfaces {
            list interface {
                key "name";
                
                leaf name {
                    type string;
                    description "Interface name";
                }
                
                container measurements {
                    description "Switch-to-switch network performance measurement data";
                    list measurement {
                        key "traffic-class protocol";
                        
                        leaf traffic-class {
                            type uint8 {
                                range "0..15";
                            }
                            description "Traffic class identifier";
                        }
                        
                        leaf protocol {
                            type enumeration {
                                enum ipv4;
                                enum ipv6;
                            }
                            description "IP protocol version used for probe packets";
                        }
                        
                        container state {
                            description "Measurement state data";
                            
                            leaf error-code {
                                type int32;
                                description "Measurement error code: 0 indicates SUCCESS, non-zero values indicate ERROR with specific error code";
                            }
                            
                            leaf error-type {
                                type string;
                                description "Error type if error-code is not equal to zero";
                            }
                            
                            leaf error-message {
                                type string;
                                description "Human-readable error message";
                            }
                            
                            leaf timestamp {
                                type uint64;
                                description "Unix timestamp of measurement";
                            }
                            
                            container latency {
                                description "Latency measurement data";
                                
                                leaf rtt {
                                    type uint64;
                                    units "microseconds";
                                    description "Round-trip time";
                                }
                            }
                        }
                    }
                }

                container histograms {
                    description "Histogram distributions for various interface metrics";
                    
                    container egress-buffer {
                        description "Egress buffer queue depth distribution";
                        
                        list traffic-class {
                            key "tc upper-boundary";
                            description "Histogram buckets per traffic class";
                            
                            leaf tc {
                                type uint8 {
                                    range "0..15";
                                }
                                description "Traffic class identifier";
                            }
                            
                            leaf upper-boundary {
                                type histogram-boundary;
                                units "bytes";
                                description "Upper boundary of the histogram bucket in bytes. Use '+Inf' for the last bucket to represent unbounded upper limit.";
                            }
                            
                            leaf count {
                                type uint64;
                                description "Number of samples in this histogram bucket";
                            }
                        }
                    }
                    
                    container ingress-buffer {
                        description "Ingress buffer queue depth distribution";
                        
                        list priority-group {
                            key "pg upper-boundary";
                            description "Histogram buckets per priority group";
                            
                            leaf pg {
                                type uint8 {
                                    range "0..7";
                                }
                                description "Priority group identifier";
                            }
                            
                            leaf upper-boundary {
                                type histogram-boundary;
                                units "bytes";
                                description "Upper boundary of the histogram bucket in bytes. Use '+Inf' for the last bucket to represent unbounded upper limit.";
                            }
                            
                            leaf count {
                                type uint64;
                                description "Number of samples in this histogram bucket";
                            }
                        }
                    }
                    
                    container counter {
                        description "Interface counter value distribution";
                        
                        list counter-type {
                            key "type upper-boundary";
                            description "Histogram buckets per counter type";
                            
                            leaf type {
                                type enumeration {
                                    enum rx-byte {
                                        description "Receive bytes counter";
                                    }
                                    enum tx-byte {
                                        description "Transmit bytes counter";
                                    }
                                    enum rx-packet {
                                        description "Receive packets counter";
                                    }
                                    enum tx-packet {
                                        description "Transmit packets counter";
                                    }
                                    enum crc {
                                        description "CRC errors counter";
                                    }
                                    enum l1-rx-byte {
                                        description "Layer 1 receive bytes counter";
                                    }
                                    enum l1-tx-byte {
                                        description "Layer 1 transmit bytes counter";
                                    }
                                }
                                description "Type of counter being measured";
                            }
                            
                            leaf upper-boundary {
                                type histogram-boundary;
                                description "Upper boundary of the histogram bucket. Use '+Inf' for the last bucket to represent unbounded upper limit.";
                            }
                            
                            leaf count {
                                type uint64;
                                description "Number of samples in this histogram bucket";
                            }
                        }
                    }
                    
                    container latency {
                        description "Packet latency distribution";
                        
                        list traffic-class {
                            key "tc upper-boundary";
                            description "Histogram buckets per traffic class";
                            
                            leaf tc {
                                type uint8 {
                                    range "0..15";
                                }
                                description "Traffic class identifier";
                            }
                            
                            leaf upper-boundary {
                                type histogram-boundary;
                                units "nanoseconds";
                                description "Upper boundary of the histogram bucket in nanoseconds. Use '+Inf' for the last bucket to represent unbounded upper limit.";
                            }
                            
                            leaf count {
                                type uint64;
                                description "Number of samples in this histogram bucket";
                            }
                        }
                    }
                }
            }
        }
    }
}
