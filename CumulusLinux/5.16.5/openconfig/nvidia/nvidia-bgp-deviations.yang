module nvidia-bgp-deviations {
  namespace "http://nvidia.com/yang/openconfig/bgp/deviations";
  prefix custom-bgp-types;

  import openconfig-network-instance { prefix oc-ni; }
  import openconfig-inet-types { prefix oc-inet; }
  organization
    "Nvidia https://www.nvidia.com";
  contact
    "NVIDIA CORPORATION & AFFILIATES
     www.nvidia.com";
  description
    "This module contains OpenConfig bgp deviation in NVidia Cumulus OS.

     Copyright (c) 2025 NVIDIA CORPORATION & AFFILIATES. All rights reserved.";

  revision 2025-02-13 {
    description
      "Initial bgp deviation file.";
    reference
      "1.0.0";
  }
  typedef neigh-address {
      type union {
          type string;
          type oc-inet:ip-address;
      }
      description "The BGP OC model expects the neighbor-name key to be an ip_address
                  type. However, for BGP unnumbered peers, the neighbor-name is in a string
                  format (e.g. peer4096/swp3s0). This definition is to support the unnumbered
                  neighbors as a string";
  }

  deviation
  "/oc-ni:network-instances/oc-ni:network-instance/oc-ni:protocols/oc-ni:protocol/oc-ni:bgp/oc-ni:neighbors/oc-ni:neighbor/oc-ni:config/oc-ni:neighbor-address"
  {
    deviate replace {
        type custom-bgp-types:neigh-address;
    }
  }
}
