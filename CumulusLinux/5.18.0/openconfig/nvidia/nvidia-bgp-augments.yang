module nvidia-bgp-augments {
  yang-version 1.1;
  namespace "http://nvidia.com/yang/openconfig/bgp/augments";
  prefix nvidia-bgp-aug;

  import openconfig-network-instance { prefix oc-ni; }
  import openconfig-bgp-types { prefix oc-bgp-types; }

  organization
    "Nvidia https://www.nvidia.com";
  contact
    "NVIDIA CORPORATION & AFFILIATES
     www.nvidia.com";
  description
    "This module contains OpenConfig bgp augments in NVidia Cumulus OS.

     Copyright (c) 2025 NVIDIA CORPORATION & AFFILIATES. All rights reserved.";

  revision 2026-07-02 {
    description
      "Add IPv4/IPv6 unreachability (SAFI 81) AFI-SAFI identities.";
    reference
      "1.1.0";
  }

  revision 2025-07-17 {
    description
      "Initial bgp augment file.";
    reference
      "1.0.0";
  }

  identity IPV4_UNREACH {
    base oc-bgp-types:AFI_SAFI_TYPE;
    description
      "IPv4 unreachability (AFI,SAFI = 1,81)";
  }

  identity IPV6_UNREACH {
    base oc-bgp-types:AFI_SAFI_TYPE;
    description
      "IPv6 unreachability (AFI,SAFI = 2,81)";
  }

   augment "/oc-ni:network-instances/oc-ni:network-instance/oc-ni:protocols/oc-ni:protocol/oc-ni:bgp/oc-ni:neighbors/oc-ni:neighbor/oc-ni:state" {
    description
      "Adds additional gracefull shutdown state information at neighbor level";

    leaf graceful-shutdown {
      type boolean;
      description
        "State information for graceful shutdown at neighbor level";
    }
  }
}
