module nvidia-platform-leak-sensor-augments {

  yang-version "1";

  // namespace
  namespace "http://nvidia.com/yang/openconfig/platform/leak-sensor/augments";

  prefix "nvidia-leak-sensor-aug";

  import openconfig-platform { prefix oc-platform; }
  import openconfig-extensions { prefix oc-ext; }


  // meta
  organization
    "Nvidia https://www.nvidia.com";
  contact
    "NVIDIA CORPORATION & AFFILIATES
     www.nvidia.com";
  description
    "This module contains OpenConfig Platform augments for leak sensor
     components in NVidia systems.
     Copyright (c) 2025 NVIDIA CORPORATION & AFFILIATES. All rights reserved.";
     
  oc-ext:openconfig-version "0.1.0";

  revision "2025-11-19" {
    description
      "Initial revision";
    reference "1.0.0";
  }

  // OpenConfig specific extensions for module metadata.
  oc-ext:regexp-posix;
  oc-ext:catalog-organization "openconfig";
  oc-ext:origin "openconfig";

  // identity statements

  // typedef statements

  // grouping statements

  grouping leak-sensor-state {
    description
      "Operational state data for leak sensor components";

    container leakage {
      description
        "Container for leak sensor operational state data";

      leaf alarm-status {
        type boolean;
        description
          "Indicates whether a leak has been detected by the sensor.
           When true, leakage has been detected. When false, no leakage
           is detected or the sensor is operating normally.";
      }
    }
  }

  // augment statements
  augment "/oc-platform:components/oc-platform:component/" +
    "oc-platform:state" {
    description
      "Adding leak sensor data to component model";

    uses leak-sensor-state;
  }
}
